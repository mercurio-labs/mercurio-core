package PictureTakingRequirements {

  requirement Req1 {
    id = "REQ-001";
    text = "The system shall focus the camera before shooting.";
  }
  
  requirement Req2 {
    id = "REQ-002";
    text = "The system shall allow shooting only after the focus is set.";
  }
  
  requirement Req321 {
    id = "REQ-003";
    text = "The system shall save the taken picture.";
  }

}
